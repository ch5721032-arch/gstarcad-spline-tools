;; spline-to-pline.lsp - Approximate splines with polylines sampled at 64 points
;; Command: SPL2PL
(defun c:SPL2PL ( / ss i en len step d pts )
  (vl-load-com)
  (setq ss (ssget '((0 . "SPLINE"))))
  (if ss
    (progn
      (setq i 0)
      (repeat (sslength ss)
        (setq en (ssname ss i))
        (setq len (vlax-curve-getDistAtParam en (vlax-curve-getEndParam en)))
        (if (and len (> len 0.0))
          (progn
            (setq step (/ len 64.0) d 0.0 pts nil)
            (while (< d len)
              (setq pts (cons (vlax-curve-getPointAtDist en d) pts))
              (setq d (+ d step))
            )
            (setq pts (cons (vlax-curve-getPointAtDist en len) pts))
            (setq pts (reverse pts))
            (command "_.PLINE")
            (foreach p pts (command p))
            (command "")
            (entdel en)
          )
        )
        (setq i (1+ i))
      )
      (princ (strcat "\nProcessed " (itoa (sslength ss)) " splines."))
    )
    (princ "\nNothing selected.")
  )
  (princ)
)
